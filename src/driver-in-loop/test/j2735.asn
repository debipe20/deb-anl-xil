J2735 DEFINITIONS AUTOMATIC TAGS ::=
BEGIN

MessageFrame ::= SEQUENCE {
    msgID INTEGER (0..255),
    value CHOICE {
        spat SPaTMessage
    }
}

SpatMessage ::= SEQUENCE {
    msgID INTEGER (0..255),
    intersectionState IntersectionState,
    phases SEQUENCE OF PhaseState
}

IntersectionState ::= SEQUENCE {
    region INTEGER (0..65535),
    id INTEGER (0..65535),
    status INTEGER (0..255),
    moy INTEGER (0..527040),   -- Minute of year
    timeStamp INTEGER (0..60000) -- Milliseconds within the current minute
}

PhaseState ::= SEQUENCE {
    id INTEGER (1..255),
    eventState ENUMERATED {
        unknown(0),
        dark(1),
        stop-And-Remain(2),
        permissive-Movement-Allowed(3),
        protected-Movement-Allowed(4),
        permissive-clearance(5),
        protected-clearance(6),
        caution-Conflicting-Traffic(7)
    },
    minEndTime INTEGER (0..3600),
    maxEndTime INTEGER (0..3600)
}

END
